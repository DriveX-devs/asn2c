EtsiTs103601Module {itu-t(0) identified-organization(4) etsi(0) itsDomain(5) wg5(5) ts(103601) p2pctlresponse(1) major-version-1(1) 
    minor-version-1(1)}
    DEFINITIONS AUTOMATIC TAGS ::= BEGIN
------------------------------------------
-- Specification of the segment message format to be used for the segmentation service.
-- Different segmentation methods are supported. One method consists in splitting the original file or message into several 
-- sequential segments (called sequential chunks). This specification can be extended to integrate transport coding methods
-- using various FEC schemes.
------------------------------------------

IMPORTS 
    HashedId8,
    Opaque,
    Psid,
    Time32,
    Uint8
FROM Ieee1609Dot2BaseTypes {iso(1) identified-organization(3) ieee(111)
    standards-association-numbered-series-standards(2) wave-stds(1609) dot2(2)
    base(1) base-types(2) major-version-2(2) minor-version-4(4)}
WITH SUCCESSORS
;

/**
* This component is the general PDU generated by the segmentation service to transmit a segment of a large message or file.
* It shall include the following components: 
*
* @field version: contains the version number of this PDU definition. For this version of this data type it shall be equal to `1`.
* 
* @field segmentationTime: contains information on when the message or file was segmented into 1 or several pieces.
* So the segmentationTime of all the segments for this message or file shall be the same.
*
* @field distributedAid:  the ITS-AID of the file. The Psid/ Its-AID is a variable length INTEGER number.
* 
* @field fileId: the id of the file to be distributed. It shall be set to the output of the SHA-256 hash function calculated on the transmitted CTL or file content.
* 
* @field segmentContent : contains the segmented data of the message or file. 
*/
SegmentPDU {Psid} ::= SEQUENCE {
    version           Uint8,
    segmentationTime  Time32,
    distributedAid    Psid,
    fileId            HashedId8,
    segmentContent	  SegmentedData,
    ...
}   

/**
* This component represents the payload of a segment/fragment of the file data. 
*/
SegmentedData ::= CHOICE {  
    seqChunks SequentialChunksSegmentedData,
    ...
}  

/**
* This component represents the payload of a segment/fragment of the file data when the sequential 
* segmentation method is used.  This method is applied in case the fileDescription is set to value 'FF'.
* It is composed of the following fields:
*
* @field messageSegmentTotalNumber: the total number of segments/fragments constituting the complete file. 
*
* @field thisMessageSegmentNumber: the number that indicates the rank or position of this segment in the ordered sequence of segments constituting the complete CTL.
*
* The fields messageSegmentTotalNumber and thisMessageSegmentNumber may be present or absent depending on the use of a network/transport
* coding technique. If network/transport coding is used, these fields are unused and shall be absent.
* Note that coding technique is not specified in the current version of the standard.
*
* @field data: this field represents the file segment/fragment payload.
* MAX value is equal to the maximum size of the payload contained in the Segment PDU, i.e. the MTU-GN - control fields size. MTU value depends
* on the network access technology and on the network layer. For instance, if ITS-G5 access layer
* and GeoNetworking SHB protocol is used, MTU-GN - GN-Header - BTP-Header = 1428 bytes and MAX value is calculated as:
* 1428  - control fields size. 
*
* All the segments, but the last one, of the original file (e.g. the full CTL) shall have the same size equal to MAX value .
*/

SequentialChunksSegmentedData ::= SEQUENCE {
    messageSegmentTotalNumber	INTEGER(1..255),
    thisMessageSegmentNumber	INTEGER(1..255),
    data                        OCTET STRING (SIZE(1..MAX))
}

/**
* The Segmented CTL Responsemessage (SCRM) is a specific Segment PDU: it uses the parametrized data type 
* SegmentedData where the psid parameter value is set to the ITS-AID value of the CTL service as specified in 
* ETSI TS 102 965 (i.e. value 624). For the SCRM message, the size of the control information ("header" fields) is 22 bytes.
*/
ctlPsid Psid ::= 624

ScrmPDU ::= SegmentPDU {Psid (ctlPsid)}

END
